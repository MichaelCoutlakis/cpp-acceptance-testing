# cpp-acceptance-testing

# Specification: Requirements Document
- ReqIF.Description: C++ Acceptance Testing: User Requirements

## UR: User Requirements (Requirement Type)

### UR-TestCase: Test Case Definition (Requirement Type)

#### UR-TestCaseDefn (Requirement Type)
Test cases shall be defined as standalone blocks of C++ code.
Example: TEST(...) { Test steps and assertions go here... }

#### UR-TestCaseStaticReg (Requirement Type)
Test cases shall be statically / automatically registered.
Explanation: there should be minimal overhead in defining a test case besides writing the block of test code.

### UR-TestRun: Test Execution (Requirement Type)

#### UR-TestRunAuto (Requirement Type)
The software shall support automatic test execution. Tests to be run shall be defined as a test suite.

#### UR-TestRunAssisted (Requirement Type)
The software shall support assisted test execution where some tests steps run automatically but operator assistance is necessary to perform some test procedures or verification steps. The shall provide capability to provide operator prompts to perform test steps and accept input verification results.

### UR-Rpt: Test Reporting (Requirement Type)

#### UR-Rpt-Gen (Requirement Type)
The software shall be capable to generate a test report in commonly used formats (HTML, ODT).

#### UR-Rpt-Traceability (Requirement Type)
The report shall show traceability from the requirements to the test requirements to the test cases. Traceability is to be defined and obtained from a ReqIF .reqif file which the software shall parse in order to determine the relations.

#### UR-Rpt-All-Asserts (Requirement Type)
The software shall be capable to generate reporting for all test assertions regardless of the pass / fail outcome of the assertion.
Note: Reporting all assertions:
- Gives a more complete picture of what was tested by inspection of the report only (without needing to retreive versioned test code)
- Retains information like measured values which would otherwise be lost if only the assertion pass result was recorded.

#### UR-Rpt-Config-Asserts (Requirement Type)
It shall be possible to dynamically configure the test assertion reporting.
Note: This is useful for test cases where assertions are repeated or too numerous to warrent reporting.

# Specification
- ReqIF.Description: C++ Acceptance Testing: Software Requirements

## SR: Software Requirements (Software Requirement)

### SR-TC: Test Cases (Software Requirement)

#### SR-TC-Macro (Software Requirement)
The software shall provide a test case macro that allows a test case to be written as a single block of C++ code
- Refines -> UR-TestCaseDefn

##### SR-TC-MacroStaticReg (Software Requirement)
The test case macro shall perform static registration
- Refines -> UR-TestCaseStaticReg

##### SR-TC-MacroSpecLink (Software Requirement)
The test case macro shall provide a means to link to the Test Requirement obtained from the ReqIF
- Refines -> UR-Rpt-Traceability

#### SR-TC-Asserts (Software Requirement)

##### SR-TC-AssertTypes (Software Requirement)
The software shall provide standard assert types, for example, logical comparisons. It shall be possible for client code to extend the assertions.
- Refines -> UR-TestCaseDefn

##### SR-TC-AssertReporting (Software Requirement)
Each assert shall provide capability to specify a message about what the assert is testing. This message will be shown in the output report
- Refines -> UR-Rpt-All-Asserts

##### SR-TC-AssertReportingConfig (Software Requirement)
Assert reporting in the output report shall be dynamically configurable. Examples include:
- All asserts (pass and fail)
- Assert reporting disabled (for example, when there are numerous asserts)
- Only failed asserts
- Refines -> UR-Rpt-All-Asserts

### SR-Ex: Test Execution (Software Requirement)

#### SR-Ex-Auto (Software Requirement)
The software shall support automatic test execution. Tests shall be defined as a test suite (example: list in .json file) or as individual test cases.
- Refines -> UR-TestRunAuto

#### SR-Ex-AssistedPromptProcedure (Software Requirement)
The software shall offer routines to prompt an assistant test user to perform test steps.
Note: Ideally, prompts could include the relevant test documentation in an appropriate document format.
- Refines -> UR-TestRunAssisted

#### SR-Ex-AssistedPromptVerification (Software Requirement)
The software shall offer routines to request and receive verification input from an assistant tester.
- Verifies -> UR-TestRunAssisted

### SR-Rpt: Test Reporting (Software Requirement)

#### SR-Rpt-Format-Config (Software Requirement)
It shall be possible to configure the output test report format
- Refines -> UR-Rpt-Gen

#### SR-Rpt-Format-HTML (Software Requirement)
HTML report format shall be supported
- Refines -> UR-Rpt-Gen

#### SR-Rpt-Format-ODT (Software Requirement)
ODT report format shall be supported
- Refines -> UR-Rpt-Gen

#### SR-Rpt-Traceability (Software Requirement)
The software shall generate a traceability / coverage report showing traceability from the requirements through to test requirements and test cases

#### SR-ReqIF (Software Requirement)

##### SR-ReqIF-Parse (Software Requirement)
The software shall parse a ReqIF file to determine traceability. Configuration shall be provided for the relation objects at each level since these are configurable.
Example: A "Refines" relation may be used from Software Requirements to User Requirements and a "Verifies" relation may be used from Test Requirements to Software Requirements.
- Refines -> UR-Rpt-Traceability

# Specification
- ReqIF.Description: C++ Acceptance Testing: Test Requirements

## TR: Test Requirements (TestRequirement)

## TR-TestCase (TestRequirement)
Confirm test cases can be written as single blocks of code which are statically registered and linked to a test requirement as per the ReqIF definition
- Verifies -> SR-TC-Macro
- Verifies -> SR-TC-MacroStaticReg
- Verifies -> SR-TC-MacroSpecLink

## TR-Asserts (TestRequirement)
Confirm test cases contain a variety of asserts with further customisation possible and configurable assert reporting level.
- Verifies -> SR-TC-AssertTypes

## TR-Report (TestRequirement)
Confirm report output format is configurable and report is generated accordingly

## TR-TestMode (TestRequirement)
Confirm test can be run either automatically or in assisted mode.

# Specification
- ReqIF.Description: C++ Acceptance Testing: Test Cases

## TC: Test Cases (TestCase)

### TC-BasicUsage (TestCase)
- TestMethod: Assisted
- TestObjective: Test the basic useage of the library. Given a ReqIF requirements file, test that a test case can be written and linked to the relevant requirement. Test that an output report is generated of the correct format containing the test asserts.
- ExpectedResult: Test report generated containing test asserts and showing traceability.
- Tests -> TR-TestCase
- Tests -> TR-Asserts
- Tests -> TR-Report

### TC-AssistedMode (TestCase)
- TestObjective: Test that test cases can operate in assisted mode by prompting the user to perform test steps and verification.
- ExpectedResult: Test executes, prompts user and receives verification input, report is generated according to assisted input.
- Tests -> TR-TestMode
